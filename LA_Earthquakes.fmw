FME workspace LA_Earthquakes.fmw
Title: MULTI to MULTI

Parameters:
- SourceDataset_SHAPEFILE_3 = $(FME_MF_DIR)Data\City_Boundary\admin_dist_SDE_DIST_DRP_CITY_COMM_BDY.shp   # Source Esri Shapefile(s)
- DestDataset_FILEGDB_5 = C:\Users\tchan\Desktop\JHU\607_SpatialDatabases\Module11\CADtoGIS.gdb   # File Geodatabase
- SourceDataset_ARCGISFEATURES_5 = https://services5.arcgis.com/7nsPwEMP38bSkCjy/arcgis/rest/services/Building_Footprints/FeatureServer/   # Host
- SourceDataset_ARCGISFEATURES_7 = https://services3.arcgis.com/bWPjFyq029ChCGur/arcgis/rest/services/Transmission_Line/FeatureServer/   # Host
- SourceDataset_ARCGISFEATURES = https://services.arcgis.com/RmCCgQtiZLDCtblq/arcgis/rest/services/admin_dist_SDE_DIST_DRP_CITY_COMM_BDY/FeatureServer/   # Host
- SourceDataset_SHAPEFILE = $(FME_MF_DIR)Data\Power_Columns_shp\power_column_point.shp   # Source Esri Shapefile(s)
- DestDataset_FILEGDB_7 = LA_Earthquake_Areas   # File Geodatabase
- DestDataset_FILEGDB_6 = LA_PowerColumn   # File Geodatabase

Readers:
- SHAPEFILE_2: SHAPEFILE from $(SourceDataset_SHAPEFILE_3)
- ARCGISFEATURES_1: ARCGISFEATURES from $(SourceDataset_ARCGISFEATURES)
- ARCGISFEATURES_2: ARCGISFEATURES from $(SourceDataset_ARCGISFEATURES_5)
- ARCGISFEATURES_3: ARCGISFEATURES from $(SourceDataset_ARCGISFEATURES_7)
- SHAPEFILE_1: SHAPEFILE from $(SourceDataset_SHAPEFILE)

Writers:
- FILEGDB_2: FILEGDB to $(DestDataset_FILEGDB_5)
- ARCGISONLINEFEATURES_1: ARCGISONLINEFEATURES
- ARCGISONLINEFEATURES_3: ARCGISONLINEFEATURES
- FILEGDB_3: FILEGDB to $(DestDataset_FILEGDB_7)
- FILEGDB_4: FILEGDB to $(DestDataset_FILEGDB_6)

Bookmark: READERS
Note: CITY BOUNDARIES: https://services.arcgis.com/RmCCgQtiZLDCtblq/arcgis/rest/services/admin_dist_SDE_DIST_DRP_CITY_COMM_BDY/FeatureServer/ [ARCGISFEATURES]
admin_dist.SDE.DIST_DRP_CITY_COMM_BDY (reader ARCGISFEATURES_1)
    attributes: OBJECTID OID, dbgis_USER2_DIST_DRP_CITY_C_2 Double, PERIMETER Double, GPLAN_INDEX2_ Integer, GPLAN_INDEX2_ID Integer, CITY Integer, CITYNAME_ALF String(30), SYMBOL_COLORNAME SmallInteger, COMP_NO SmallInteger, TYPE String(10), ADOPTED String(8), SYMBOL SmallInteger, NAME String(50), ACRES Double, CITY_COMM_NAME String(50), ZCIP_PHASE String(3), SQ_MILES Double, JURISDICTION String(50), area_1 Double, dbgis_USER2_DIST_DRP_CITY_C_20 Double, Shape__Area Double, Shape__Length Double, GlobalID GlobalID(38)
    -> Reprojector
Note: TRANSMISSION LINES: https://services3.arcgis.com/bWPjFyq029ChCGur/arcgis/rest/services/Transmission_Line/FeatureServer/ [ARCGISFEATURES]
Transmission Line (reader ARCGISFEATURES_3) [off]
    attributes: OBJECTID OID, Name String(50), kV String(50), kV_Sort Double, Owner String(50), Status String(20), Circuit String(50), Type String(50), Legend String(100), Length_Mile Double, Length_Feet String(50), TLine_Name String(120), Source String(50), Comments String(100), Creator String(50), Creator_Date Date, Last_Editor String(50), Last_Editor_Date Date, GlobalID GlobalID(38), Shape__Length Double
    -> Reprojector_2
Note: POWER COLUMNS/POLES: https://mygeodata.cloud/data/download/osm/power-columns-or-poles/united-states-of-america--california/los-angeles-county/los-angeles [SHAPEFILE]
power_column_point (reader SHAPEFILE_1)
    attributes: power varchar(80), ele varchar(80), name varchar(80), wpt_symbol varchar(80), material varchar(80), circuits varchar(80), design varchar(80), highway varchar(80), operator varchar(80), structure varchar(80)
    -> Reprojector_3
Note: BUILDING FOOTPRINTS: https://services5.arcgis.com/7nsPwEMP38bSkCjy/arcgis/rest/services/Building_Footprints/FeatureServer/ [ARCGISFEATURES]
Building_Footprints (reader ARCGISFEATURES_2) [off]
    attributes: OBJECTID OID, CODE String(50), BLD_ID String(20), HEIGHT Double, ELEV Double, AREA Double, LARIAC_SOURCE String(25), LARIAC_DATE String(4), AIN String(10), STATUS String(50), CODE_NUM SmallInteger
    -> Reprojector_4

Bookmark: REPROJECT TO EPSG:32611
Reprojector
    DEST = EPSG:32611
    INTERPOLATION_TYPE_NAME = Nearest Neighbor
    RASTER_CELL_SIZE = Preserve Cells
    RASTER_TOLERANCE = 0.0
    REPROJECTED -> CoordinateSystemSetter_2
CoordinateSystemSetter_2
    COORDSYS = EPSG:32611
    -> TestFilter
Reprojector_2
    DEST = EPSG:32611
    INTERPOLATION_TYPE_NAME = Nearest Neighbor
    RASTER_CELL_SIZE = Preserve Cells
    RASTER_TOLERANCE = 0.0
    REPROJECTED -> CoordinateSystemSetter
CoordinateSystemSetter
    COORDSYS = EPSG:32611
    -> AttributeFilter
Reprojector_3
    DEST = EPSG:32611
    INTERPOLATION_TYPE_NAME = Nearest Neighbor
    RASTER_CELL_SIZE = Preserve Cells
    RASTER_TOLERANCE = 0.0
    REPROJECTED -> CoordinateSystemSetter_3
CoordinateSystemSetter_3
    COORDSYS = EPSG:32611
    -> AttributeFilter_2
Reprojector_4
    DEST = EPSG:32611
    INTERPOLATION_TYPE_NAME = Nearest Neighbor
    RASTER_CELL_SIZE = Preserve Cells
    RASTER_TOLERANCE = 0.0
    REPROJECTED -> CoordinateSystemSetter_4
CoordinateSystemSetter_4
    COORDSYS = EPSG:32611
    -> AttributeCreator_3

Bookmark: LAYER-SPECIFIC PROCESSING
Note: Filter for Los Angeles
TestFilter
    DEFAULT_VALUE = <UNFILTERED>
    PASSED_TEST_GROUP_OUTPUT = FIRST
    TEST_LIST = "BOOL_OP,OR,COMPOSITE_TEST,""""""1"""""",TEST_CLAUSE,TEST @Value(CITYNAME_ALF) = LOS ANGELES",LOS ANGELES
    LOS ANGELES -> AttributeKeeper_2
Note: Filter for status operational or missing (excludes proposed)
AttributeFilter
    ATTR_NAME = Status
    ATTR_VALUES = Operational,<Empty>,<Missing>,<Null>,<Unfiltered>
    Operational -> Clipper [CANDIDATE]
Note: Separate by power attribute
AttributeFilter_2
    ATTR_NAME = power
    ATTR_VALUES = pole,tower,<Empty>,<Missing>,<Null>,<Unfiltered>
    pole -> AttributeCreator
    tower -> AttributeCreator_2
Note: Add height attribute: / power pole = 60ft / power towers = 150ft
AttributeCreator
    ATTR_TABLE = SET_TO height_ft (int16) = 60
    -> Clipper_2 [CANDIDATE]
AttributeCreator_2
    ATTR_TABLE = SET_TO height_ft (int16) = 150
    -> Clipper_2 [CANDIDATE]
Note: Create HEIGHT_MULTIPLIER value (1.5)
AttributeCreator_3
    ATTR_TABLE = SET_TO HEIGHT_MULTIPLIER (real32) = 1.5
    -> Clipper_3 [CANDIDATE]

Bookmark: MANAGE ATTRIBUTES
AttributeKeeper_2
    CREATE_BULK_MODE_FEATURES = NO
    KEEP_ATTRS = CITY_COMM_NAME,Shape__Area,Shape__Length,SQ_MILES
    -> AttributeManager
AttributeManager
    ATTR_TABLE:
      RENAME_SET_VALUE CITY_COMM_NAME > CITYNAME (varchar(50))
      RENAME_SET_VALUE SQ_MILES > SQMILES (real64)
      RENAME_SET_VALUE Shape__Area > AREA (real64)
      RENAME_SET_VALUE Shape__Length > PERIMETER (real64)
    -> Clipper [CLIPPER]
    -> Clipper_2 [CLIPPER]
    -> Clipper_3 [CLIPPER]
    -> LA_City (writer FILEGDB_4)
AttributeManager_3
    ATTR_TABLE:
      REMOVE Owner (varchar(50))
      REMOVE Status (varchar(20))
      REMOVE Circuit (varchar(50))
      REMOVE Type (varchar(50))
      REMOVE Legend (varchar(100))
      REMOVE TLine_Name (varchar(120))
      REMOVE Source (varchar(50))
      REMOVE _clipped (char(3))
    USER_EXPOSED_ATTRIBUTES = Length_Mile,Length_Feet,Creator_Date,Last_Editor,Last_Editor_Date
    -> Dissolver
AttributeKeeper
    CREATE_BULK_MODE_FEATURES = NO
    KEEP_ATTRS = power,height_ft
    -> Dissolver_2
AttributeKeeper_4
    CREATE_BULK_MODE_FEATURES = NO
    KEEP_ATTRS = power,height_ft
    -> Power_Column (writer FILEGDB_3)
AttributeKeeper_5
    CREATE_BULK_MODE_FEATURES = NO
    KEEP_ATTRS = AREA,BLD_ID,ELEV,HEIGHT,OBJECTID
    -> Building_Footprint (writer FILEGDB_3)
AttributeKeeper_3
    CREATE_BULK_MODE_FEATURES = NO
    KEEP_ATTRS = AREA,BLD_ID,ELEV,HEIGHT,OBJECTID,HEIGHT_MULTIPLIER
    -> Bufferer_4

Bookmark: OUTPUT TO "LA_Earthquake" GEODATABASE
Note: LA City (polygon)
LA_City (writer FILEGDB_4)
    attributes: CITYNAME text(50), SQMILES double, AREA double, PERIMETER double
Note: Transmission Line (polylines)
Transmission_Line (writer FILEGDB_3)
    attributes: OBJECTID int, Name text(50), kV text(50), GlobalID text(38), Comments text(100), Creator text(50), kV_Sort double, Length_Mile double, Length_Feet text(50), Creator_Date date, Last_Editor text(50), Last_Editor_Date date, Shape__Length double
Transmission_Line_Buffer (writer FILEGDB_3)
    attributes: OBJECTID int, Name text(50), kV text(50), GlobalID text(38), Comments text(100), Creator text(50), kV_Sort double, Length_Mile double, Length_Feet text(50), Creator_Date date, Last_Editor text(50), Last_Editor_Date date, Shape__Length double
Power_Column_Buffer (writer FILEGDB_4)
    attributes: height_ft smallint, power text(80)
Note: Power Column (points)
Power_Column (writer FILEGDB_3) [off]
    attributes: height_ft smallint, power text(80)
Note: LA Building Footprint (polygons)
Building_Footprint (writer FILEGDB_3)
    attributes: OBJECTID int, BLD_ID text(20), HEIGHT double, ELEV double, AREA double
Building_Footprint_Buffer (writer FILEGDB_3)
    attributes: HEIGHT_MULTIPLIER single, OBJECTID int, BLD_ID text(20), HEIGHT double, ELEV double, AREA double

Bookmark: CLIP w/ LA BOUNDARY
Clipper
    ADD_NODATA = YES
    BOUNDARY_CASES = INSIDE
    CLEANING_TOLERANCE = Automatic
    CLIPPED_ATTR = _clipped
    GENERATE_LIST = NO
    INVALID_PARTS_HANDLING = REJECT_PARTS
    MISSING_M_MODE = Linear Interpolation
    MISSING_Z_MODE = Planar Interpolation
    MULTIPLE_CLIPPERS = NO
    M_VAL_SOURCE = CANDIDATE
    PRESERVE_RASTER_EXTENTS = NO
    RASTER_CELL_MODE = CENTER
    Z_VAL_SOURCE = CANDIDATE
    INSIDE -> Bufferer
    INSIDE -> AttributeManager_2
Clipper_2
    ADD_NODATA = YES
    BOUNDARY_CASES = INSIDE
    CLEANING_TOLERANCE = Automatic
    CLIPPED_ATTR = _clipped
    GENERATE_LIST = NO
    INVALID_PARTS_HANDLING = REJECT_PARTS
    MISSING_M_MODE = Linear Interpolation
    MISSING_Z_MODE = Planar Interpolation
    MULTIPLE_CLIPPERS = NO
    M_VAL_SOURCE = CANDIDATE
    PRESERVE_RASTER_EXTENTS = NO
    RASTER_CELL_MODE = CENTER
    Z_VAL_SOURCE = CANDIDATE
    INSIDE -> Bufferer_2
    INSIDE -> AttributeKeeper_4
Clipper_3
    ADD_NODATA = YES
    BOUNDARY_CASES = INSIDE
    CLEANING_TOLERANCE = Automatic
    CLIPPED_ATTR = _clipped
    GENERATE_LIST = NO
    INVALID_PARTS_HANDLING = REJECT_PARTS
    MISSING_M_MODE = Linear Interpolation
    MISSING_Z_MODE = Planar Interpolation
    MULTIPLE_CLIPPERS = NO
    M_VAL_SOURCE = CANDIDATE
    PRESERVE_RASTER_EXTENTS = NO
    RASTER_CELL_MODE = CENTER
    Z_VAL_SOURCE = CANDIDATE
    INSIDE -> AttributeKeeper_3
    INSIDE -> AttributeKeeper_5

Bookmark: BUFFER
AttributeManager_2
    ATTR_TABLE:
      REMOVE Owner (varchar(50))
      REMOVE Status (varchar(20))
      REMOVE Circuit (varchar(50))
      REMOVE Type (varchar(50))
      REMOVE Legend (varchar(100))
      REMOVE TLine_Name (varchar(120))
      REMOVE Source (varchar(50))
      REMOVE _clipped (char(3))
    USER_EXPOSED_ATTRIBUTES = Length_Mile,Length_Feet,Creator_Date,Last_Editor,Last_Editor_Date
    -> Transmission_Line (writer FILEGDB_3)
Note: Buffer by 35ft
Bufferer
    ANGLE = 22.5
    CAP_STYLE = Arc
    CORNER_STYLE = Arc
    MODE = AREA
    OFFSET = 35
    OFFSET_UNITS = FEET
    PRECISION = APPROX
    BUFFERED -> AttributeManager_3
Note: Buffer by height
Bufferer_2
    ANGLE = 22.5
    CAP_STYLE = Arc
    CORNER_STYLE = Arc
    MODE = AREA
    OFFSET = @Value(height_ft)
    OFFSET_UNITS = FEET
    PRECISION = APPROX
    BUFFERED -> AttributeKeeper
Note: (@Value(HEIGHT))* / (@Value(HEIGHT_MULTIPLIER))
Note: Buffer by 1.5x height
Bufferer_4
    ANGLE = 22.5
    CAP_STYLE = Arc
    CORNER_STYLE = Arc
    MODE = AREA
    OFFSET = (@Value(HEIGHT))*(@Value(HEIGHT_MULTIPLIER))
    OFFSET_UNITS = NONE
    PRECISION = APPROX
    BUFFERED -> Building_Footprint_Buffer (writer FILEGDB_3)

Bookmark: DISSOLVE
Dissolver
    ACCUM_INPUT_ATTRS = Use Attributes From One Feature
    CLEANING_TOLERANCE = Automatic
    CONNECT_Z_MODE = First Wins
    DEAGGREGATE_INPUT = Yes
    AREA -> Transmission_Line_Buffer (writer FILEGDB_3)
Dissolver_2
    ACCUM_INPUT_ATTRS = Use Attributes From One Feature
    CLEANING_TOLERANCE = Automatic
    CONNECT_Z_MODE = First Wins
    DEAGGREGATE_INPUT = Yes
    AREA -> Power_Column_Buffer (writer FILEGDB_4)
